IEEE1609dot2-Peer2Peer {iso(1) identified-organization(3) ieee(111) 
standards-association-numbered-series-standards(2) wave-stds(1609)  
dot2(2) management (2) peer-to-peer (1) major-version-2(2)}

--********************************************************************** 
-- 
-- Data types for Peer-to-peer distribution of IEEE P1609.2 support data 
-- 
-- Associated with a two-byte PSID to be assigned.
-- When broadcast over WSMP, to be encoded with OER. 
--
--********************************************************************** 

DEFINITIONS AUTOMATIC TAGS ::= BEGIN

EXPORTS ALL;
 
IMPORTS 
  Uint8
FROM IEEE1609dot2BaseTypes {iso(1) identified-organization(3) ieee(111) 
    standards-association-numbered-series-standards(2) wave-stds(1609)  
    dot2(2) base(1) base-types(2) major-version-2 (2)}


  Certificate
FROM IEEE1609dot2 {iso(1) identified-organization(3) ieee(111) 
    standards-association-numbered-series-standards(2) wave-stds(1609)  
    dot2(2) base(1) schema(1) major-version-2 (2)}
;

Ieee1609dot2Peer2PeerPDU ::= SEQUENCE {
  version            Uint8(1),
  content            CHOICE {
    caCerts            CaCertP2pPDU,
    ...
  }
}

CaCertP2pPDU::= SEQUENCE OF Certificate

END
