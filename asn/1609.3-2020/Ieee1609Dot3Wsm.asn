Ieee1609Dot3Wsm {iso(1) identified-organization(3) ieee(111) standards-association-numbered-series-standards(2) wave-stds(1609) dot3(3) wsm(2) major-version-1 (1) minor-version-1(1)}

DEFINITIONS AUTOMATIC TAGS ::= 
BEGIN
/* Quality check info:
Proper syntax and correct mapping of UPER on the intended binary presentation as specified in the main body of this document was validated with the OSS ASN.1 Studio tool.
*/
IMPORTS
VarLengthNumber, EXT-TYPE, Extension, RefExt, c-CompactTimeConfidence, c-ChannelLoad, c-Reserved, c-TxPowerUsed80211, c-DataRate80211, c-ChannelNumber80211, CompactTimeConfidence, ChannelNumber80211, DataRate80211, TXpower80211 FROM Ieee1609Dot3Wee {iso(1) identified-organization(3) ieee(111) standards-association-numbered-series-standards(2) wave-stds(1609) dot3(3) wee(1) major-version-1(1) minor-version-1(1)};
-- End of IMPORTS
--
-- The following defines the WSM data frame as described in 
-- subclause 8.3
--
ShortMsgNpdu ::= SEQUENCE { 
	subtype	ShortMsgSubtype,
       -- Indicates the networking protocol features provided, see
       -- Table 20
	transport	ShortMsgTpdus,
       -- Selects a transport protocol feature. 
       -- In this standard, only TPID values 0 and 1, consistent with
       -- addressing using PSIDs is supported, see Table 21
	body	ShortMsgData
       -- Contains higher layer information to be transported, 
       -- see subclause 8.3.5
}
--
-- Sub-Types
-- UPER encoding of ShortMsgSubtype produces a 4-bit tag number
-- represented by the Subtype field of the WSMP-N-Header, 
-- see subclause 8.3.2.
-- Processing of type NoSubtypeProcessing is not specified in
-- this version of the standard.
--
ShortMsgSubtype ::= CHOICE {
	nullNetworking	[0] NullNetworking,
       -- Selects subtype 0 Null-networking protocol, see Table 20
	subTypeReserved1	[1] NoSubtypeProcessing, -- reserved for ISO
	subTypeReserved2	[2] NoSubtypeProcessing, -- reserved for ISO
	subTypeReserved3	[3] NoSubtypeProcessing, -- reserved for ISO
	subTypeReserved4	[4] NoSubtypeProcessing, -- reserved for ISO
	subTypeReserved5	[5] NoSubtypeProcessing, -- reserved for ISO
	subTypeReserved6	[6] NoSubtypeProcessing, -- reserved for ISO
	subTypeReserved7	[7] NoSubtypeProcessing, -- reserved for ISO
	subTypeReserved8	[8] NoSubtypeProcessing,
	subTypeReserved9	[9] NoSubtypeProcessing,
	subTypeReserved19	[10] NoSubtypeProcessing,
	subTypeReserved11	[11] NoSubtypeProcessing,
	subTypeReserved12	[12] NoSubtypeProcessing,
	subTypeReserved13	[13] NoSubtypeProcessing,
	subTypeReserved14	[14] NoSubtypeProcessing,
	subTypeReserved15	[15] NoSubtypeProcessing
}
NoSubtypeProcessing ::= SEQUENCE {
	optBit	BIT STRING (SIZE(1)), -- always set to '0'b
	version	ShortMsgVersion -- set to c-shortMsgVersionNo
}
--
-- The following defines the WSMP Version field of the WSMP-N-Header,
-- see subclause 8.3.2.
--
ShortMsgVersion ::= INTEGER (0..7)
--
-- The following defines the value of the WSMP Version field. 
--
c-shortMsgVersionNo	ShortMsgVersion ::= 3
--
-- The following specifies the format of the ShortMsgSubtype 
-- when Subtype is 0 (Null-networking). See also subclause 8.3.2.
--
NullNetworking ::= SEQUENCE {
	version	ShortMsgVersion, -- set to c-shortMsgVersionNo
	nExtensions	ShortMsgNextensions OPTIONAL
}
-- 
-- The following defines WAVE Information Element Extension fields
-- defined for the WSMP-N-Header, see subclause 8.3.4. 
--
-- Sequence of 0 to n extension elements
ShortMsgNextensions ::= SEQUENCE OF ShortMsgNextension
-- A single extension element
ShortMsgNextension ::= Extension{{ShortMsgNexts}}
-- All available N-Extensions
ShortMsgNexts EXT-TYPE ::= {
	{ TXpower80211          IDENTIFIED BY c-TxPowerUsed80211 } |
	{ ChannelNumber80211    IDENTIFIED BY c-ChannelNumber80211 } |
	{ DataRate80211         IDENTIFIED BY c-DataRate80211 } |
     -- {ChannelLoad IDENTIFIED BY c-ChannelLoad} |
     -- ChannelLoad is not specified in this standard.
	{ CompactTimeConfidence IDENTIFIED BY c-CompactTimeConfidence },
	...
}
--
-- ShortMsgTpdus is used to specify the transport protocol features
-- encoded in the WSMP-T-Header. See subclause 8.3.2.2.
-- UPER encoding of ShortMsgTpdus produces a 7-bit tag number,
-- represented by the TPID field of the WSMP-T-Header.
-- The CHOICE ShortMsgBcPDU selects the transport protocol where
-- PSID is used as the destination address. 
-- Processing of type NoTpidProcessing is not specified in
-- this version of the standard.
--
ShortMsgTpdus ::= CHOICE {
 	bcMode	[0] ShortMsgBcPDU,
	tpidReserved1	[1] NoTpidProcessing, -- reserved for ISO
	tpidReserved2	[2] NoTpidProcessing, -- reserved for ISO
	tpidReserved3	[3] NoTpidProcessing, -- reserved for ISO
	tpidReserved4	[4] NoTpidProcessing, -- reserved for ISO
	tpidReserved5	[5] NoTpidProcessing, -- reserved for ISO
	tpidReserved6	[6] NoTpidProcessing, -- reserved for ISO
	tpidReserved7	[7] NoTpidProcessing, -- reserved for ISO
	tpidReserved8	[8] NoTpidProcessing, -- reserved for ISO
	tpidReserved9	[9] NoTpidProcessing, -- reserved for ISO
	tpidReserved10	[10] NoTpidProcessing, -- reserved for ISO
	tpidReserved11	[11] NoTpidProcessing,
	tpidReserved12	[12] NoTpidProcessing,
	tpidReserved13	[13] NoTpidProcessing,
	tpidReserved14	[14] NoTpidProcessing,
	tpidReserved15	[15] NoTpidProcessing,
	tpidReserved16	[16] NoTpidProcessing,
	tpidReserved17	[17] NoTpidProcessing,
	tpidReserved18	[18] NoTpidProcessing,
	tpidReserved19	[19] NoTpidProcessing,
	tpidReserved20	[20] NoTpidProcessing,
	tpidReserved21	[21] NoTpidProcessing,
	tpidReserved22	[22] NoTpidProcessing,
	tpidReserved23	[23] NoTpidProcessing,
	tpidReserved24	[24] NoTpidProcessing,
	tpidReserved25	[25] NoTpidProcessing,
	tpidReserved26	[26] NoTpidProcessing,
	tpidReserved27	[27] NoTpidProcessing,
	tpidReserved28	[28] NoTpidProcessing,
	tpidReserved29	[29] NoTpidProcessing,
	tpidReserved30	[30] NoTpidProcessing,
	tpidReserved31	[31] NoTpidProcessing,
	tpidReserved32	[32] NoTpidProcessing,
	tpidReserved33	[33] NoTpidProcessing,
	tpidReserved34	[34] NoTpidProcessing,
	tpidReserved35	[35] NoTpidProcessing,
	tpidReserved36	[36] NoTpidProcessing,
	tpidReserved37	[37] NoTpidProcessing,
	tpidReserved38	[38] NoTpidProcessing,
	tpidReserved39	[39] NoTpidProcessing,
	tpidReserved40	[40] NoTpidProcessing,
	tpidReserved41	[41] NoTpidProcessing,
	tpidReserved42	[42] NoTpidProcessing,
	tpidReserved43	[43] NoTpidProcessing,
	tpidReserved44	[44] NoTpidProcessing,
	tpidReserved45	[45] NoTpidProcessing,
	tpidReserved46	[46] NoTpidProcessing,
	tpidReserved47	[47] NoTpidProcessing,
	tpidReserved48	[48] NoTpidProcessing,
	tpidReserved49	[49] NoTpidProcessing,
	tpidReserved50	[50] NoTpidProcessing,
	tpidReserved51	[51] NoTpidProcessing,
	tpidReserved52	[52] NoTpidProcessing,
	tpidReserved53	[53] NoTpidProcessing,
	tpidReserved54	[54] NoTpidProcessing,
	tpidReserved55	[55] NoTpidProcessing,
	tpidReserved56	[56] NoTpidProcessing,
	tpidReserved57	[57] NoTpidProcessing,
	tpidReserved58	[58] NoTpidProcessing,
	tpidReserved59	[59] NoTpidProcessing,
	tpidReserved60	[60] NoTpidProcessing,
	tpidReserved61	[61] NoTpidProcessing,
	tpidReserved62	[62] NoTpidProcessing,
	tpidReserved63	[63] NoTpidProcessing,
	tpidReserved64	[64] NoTpidProcessing,
	tpidReserved65	[65] NoTpidProcessing,
	tpidReserved66	[66] NoTpidProcessing,
	tpidReserved67	[67] NoTpidProcessing,
	tpidReserved68	[68] NoTpidProcessing,
	tpidReserved69	[69] NoTpidProcessing,
	tpidReserved70	[70] NoTpidProcessing,
	tpidReserved71	[71] NoTpidProcessing,
	tpidReserved72	[72] NoTpidProcessing,
	tpidReserved73	[73] NoTpidProcessing,
	tpidReserved74	[74] NoTpidProcessing,
	tpidReserved75	[75] NoTpidProcessing,
	tpidReserved76	[76] NoTpidProcessing,
	tpidReserved77	[77] NoTpidProcessing,
	tpidReserved78	[78] NoTpidProcessing,
	tpidReserved79	[79] NoTpidProcessing,
	tpidReserved80	[80] NoTpidProcessing,
	tpidReserved81	[81] NoTpidProcessing,
	tpidReserved82	[82] NoTpidProcessing,
	tpidReserved83	[83] NoTpidProcessing,
	tpidReserved84	[84] NoTpidProcessing,
	tpidReserved85	[85] NoTpidProcessing,
	tpidReserved86	[86] NoTpidProcessing,
	tpidReserved87	[87] NoTpidProcessing,
	tpidReserved88	[88] NoTpidProcessing,
	tpidReserved89	[89] NoTpidProcessing,
	tpidReserved90	[90] NoTpidProcessing,
	tpidReserved91	[91] NoTpidProcessing,
	tpidReserved92	[92] NoTpidProcessing,
	tpidReserved93	[93] NoTpidProcessing,
	tpidReserved94	[94] NoTpidProcessing,
	tpidReserved95	[95] NoTpidProcessing,
	tpidReserved96	[96] NoTpidProcessing,
	tpidReserved97	[97] NoTpidProcessing,
	tpidReserved98	[98] NoTpidProcessing,
	tpidReserved99	[99] NoTpidProcessing,
	tpidReserved100	[100] NoTpidProcessing,
	tpidReserved101	[101] NoTpidProcessing,
	tpidReserved102	[102] NoTpidProcessing,
	tpidReserved103	[103] NoTpidProcessing,
	tpidReserved104	[104] NoTpidProcessing,
	tpidReserved105	[105] NoTpidProcessing,
	tpidReserved106	[106] NoTpidProcessing,
	tpidReserved107	[107] NoTpidProcessing,
	tpidReserved108	[108] NoTpidProcessing,
	tpidReserved109	[109] NoTpidProcessing,
	tpidReserved110	[110] NoTpidProcessing,
	tpidReserved111	[111] NoTpidProcessing,
	tpidReserved112	[112] NoTpidProcessing,
	tpidReserved113	[113] NoTpidProcessing,
	tpidReserved114	[114] NoTpidProcessing,
	tpidReserved115	[115] NoTpidProcessing,
	tpidReserved116	[116] NoTpidProcessing,
	tpidReserved117	[117] NoTpidProcessing,
	tpidReserved118	[118] NoTpidProcessing,
	tpidReserved119	[119] NoTpidProcessing,
	tpidReserved120	[120] NoTpidProcessing,
	tpidReserved121	[121] NoTpidProcessing,
	tpidReserved122	[122] NoTpidProcessing,
	tpidReserved123	[123] NoTpidProcessing,
	tpidReserved124	[124] NoTpidProcessing,
	tpidReserved125	[125] NoTpidProcessing,
	tpidReserved126	[126] NoTpidProcessing,
	tpidReserved127	[127] NoTpidProcessing
}
NoTpidProcessing ::= BIT STRING (SIZE(1)) 

--
-- The following specifies the Address Info and WAVE Information
-- Element Extensions fields of the WSMP-T-Header, see subclause 8.3.3.
-- The ShortMsgBcPDU selects the transport protocol where PSID is used
-- as the destination address. 
--
ShortMsgBcPDU ::= SEQUENCE {
	addrInfo	VarLengthNumber, -- PSID
	tExtensions	ShortMsgTexts OPTIONAL
}
--
-- The following specifies WSM Length field of the WSMP-T-Header, 
-- see subclause 8.3.3.4, and also the WSM Data field, 
-- see subclause 8.3.5
--
ShortMsgData ::= OCTET STRING
 -- Maximum size is given by access technology
-- 
-- The following defines WAVE Information Element Extension fields
-- defined for the WSMP-T-Header. This version of the standard has not
-- defined any information elements for the WSMP-T-Header, see
-- subclause 8.3.4. The following are place holders for future use.
--
-- Sequence of 0 to n T-Extension elements
ShortMsgTexts ::= SEQUENCE OF ShortMsgText
-- A single T-Extension element
ShortMsgText ::= Extension{{ShortMsgTextTypes}}
-- 
-- All available T-Extensions
-- None are defined so far. Once at least one is defined, the below
-- DummyExtension can be removed.
--
ShortMsgTextTypes EXT-TYPE ::= {
	{ DummyExtension	IDENTIFIED BY c-Reserved },
	...
}
DummyExtension ::= NULL
END
